package InheritanceBaseline {
part def Base { attribute identifier; }
part def T0 :> Base { attribute f0; }
part def T1 :> T0 { attribute f1; }
part def T2 :> T1 { attribute f2; }
part def T3 :> T2 { attribute f3; }
part def T4 :> T3 { attribute f4; }
part def T5 :> T4 { attribute f5; }
part def T6 :> T5 { attribute f6; }
part def T7 :> T6 { attribute f7; }
part def T8 :> T7 { attribute f8; }
part def T9 :> T8 { attribute f9; }
part def T10 :> T9 { attribute f10; }
part def T11 :> T10 { attribute f11; }
part def T12 :> T11 { attribute f12; }
part def T13 :> T12 { attribute f13; }
part def T14 :> T13 { attribute f14; }
part def T15 :> T14 { attribute f15; }
part def T16 :> T15 { attribute f16; }
part def T17 :> T16 { attribute f17; }
part def T18 :> T17 { attribute f18; }
part def T19 :> T18 { attribute f19; }
part def T20 :> T19 { attribute f20; }
part def T21 :> T20 { attribute f21; }
part def T22 :> T21 { attribute f22; }
part def T23 :> T22 { attribute f23; }
part def T24 :> T23 { attribute f24; }
part def T25 :> T24 { attribute f25; }
part def T26 :> T25 { attribute f26; }
part def T27 :> T26 { attribute f27; }
part def T28 :> T27 { attribute f28; }
part def T29 :> T28 { attribute f29; }
part def T30 :> T29 { attribute f30; }
part def T31 :> T30 { attribute f31; }
part def T32 :> T31 { attribute f32; }
part def T33 :> T32 { attribute f33; }
part def T34 :> T33 { attribute f34; }
part def T35 :> T34 { attribute f35; }
part def T36 :> T35 { attribute f36; }
part def T37 :> T36 { attribute f37; }
part def T38 :> T37 { attribute f38; }
part def T39 :> T38 { attribute f39; }
part instance0 : T39;
part instance1 : T39;
part instance2 : T39;
part instance3 : T39;
part instance4 : T39;
part instance5 : T39;
part instance6 : T39;
part instance7 : T39;
part instance8 : T39;
part instance9 : T39;
part instance10 : T39;
part instance11 : T39;
part instance12 : T39;
part instance13 : T39;
part instance14 : T39;
part instance15 : T39;
part instance16 : T39;
part instance17 : T39;
part instance18 : T39;
part instance19 : T39;
part instance20 : T39;
part instance21 : T39;
part instance22 : T39;
part instance23 : T39;
part instance24 : T39;
part instance25 : T39;
part instance26 : T39;
part instance27 : T39;
part instance28 : T39;
part instance29 : T39;
part instance30 : T39;
part instance31 : T39;
part instance32 : T39;
part instance33 : T39;
part instance34 : T39;
part instance35 : T39;
part instance36 : T39;
part instance37 : T39;
part instance38 : T39;
part instance39 : T39;
part instance40 : T39;
part instance41 : T39;
part instance42 : T39;
part instance43 : T39;
part instance44 : T39;
part instance45 : T39;
part instance46 : T39;
part instance47 : T39;
part instance48 : T39;
part instance49 : T39;
part instance50 : T39;
part instance51 : T39;
part instance52 : T39;
part instance53 : T39;
part instance54 : T39;
part instance55 : T39;
part instance56 : T39;
part instance57 : T39;
part instance58 : T39;
part instance59 : T39;
part instance60 : T39;
part instance61 : T39;
part instance62 : T39;
part instance63 : T39;
part instance64 : T39;
part instance65 : T39;
part instance66 : T39;
part instance67 : T39;
part instance68 : T39;
part instance69 : T39;
part instance70 : T39;
part instance71 : T39;
part instance72 : T39;
part instance73 : T39;
part instance74 : T39;
part instance75 : T39;
part instance76 : T39;
part instance77 : T39;
part instance78 : T39;
part instance79 : T39;
part instance80 : T39;
part instance81 : T39;
part instance82 : T39;
part instance83 : T39;
part instance84 : T39;
part instance85 : T39;
part instance86 : T39;
part instance87 : T39;
part instance88 : T39;
part instance89 : T39;
part instance90 : T39;
part instance91 : T39;
part instance92 : T39;
part instance93 : T39;
part instance94 : T39;
part instance95 : T39;
part instance96 : T39;
part instance97 : T39;
part instance98 : T39;
part instance99 : T39;
part instance100 : T39;
part instance101 : T39;
part instance102 : T39;
part instance103 : T39;
part instance104 : T39;
part instance105 : T39;
part instance106 : T39;
part instance107 : T39;
part instance108 : T39;
part instance109 : T39;
part instance110 : T39;
part instance111 : T39;
part instance112 : T39;
part instance113 : T39;
part instance114 : T39;
part instance115 : T39;
part instance116 : T39;
part instance117 : T39;
part instance118 : T39;
part instance119 : T39;
part instance120 : T39;
part instance121 : T39;
part instance122 : T39;
part instance123 : T39;
part instance124 : T39;
part instance125 : T39;
part instance126 : T39;
part instance127 : T39;
part instance128 : T39;
part instance129 : T39;
part instance130 : T39;
part instance131 : T39;
part instance132 : T39;
part instance133 : T39;
part instance134 : T39;
part instance135 : T39;
part instance136 : T39;
part instance137 : T39;
part instance138 : T39;
part instance139 : T39;
part instance140 : T39;
part instance141 : T39;
part instance142 : T39;
part instance143 : T39;
part instance144 : T39;
part instance145 : T39;
part instance146 : T39;
part instance147 : T39;
part instance148 : T39;
part instance149 : T39;
part instance150 : T39;
part instance151 : T39;
part instance152 : T39;
part instance153 : T39;
part instance154 : T39;
part instance155 : T39;
part instance156 : T39;
part instance157 : T39;
part instance158 : T39;
part instance159 : T39;
part instance160 : T39;
part instance161 : T39;
part instance162 : T39;
part instance163 : T39;
part instance164 : T39;
part instance165 : T39;
part instance166 : T39;
part instance167 : T39;
part instance168 : T39;
part instance169 : T39;
part instance170 : T39;
part instance171 : T39;
part instance172 : T39;
part instance173 : T39;
part instance174 : T39;
part instance175 : T39;
part instance176 : T39;
part instance177 : T39;
part instance178 : T39;
part instance179 : T39;
part instance180 : T39;
part instance181 : T39;
part instance182 : T39;
part instance183 : T39;
part instance184 : T39;
part instance185 : T39;
part instance186 : T39;
part instance187 : T39;
part instance188 : T39;
part instance189 : T39;
part instance190 : T39;
part instance191 : T39;
part instance192 : T39;
part instance193 : T39;
part instance194 : T39;
part instance195 : T39;
part instance196 : T39;
part instance197 : T39;
part instance198 : T39;
part instance199 : T39;
part instance200 : T39;
part instance201 : T39;
part instance202 : T39;
part instance203 : T39;
part instance204 : T39;
part instance205 : T39;
part instance206 : T39;
part instance207 : T39;
part instance208 : T39;
part instance209 : T39;
part instance210 : T39;
part instance211 : T39;
part instance212 : T39;
part instance213 : T39;
part instance214 : T39;
part instance215 : T39;
part instance216 : T39;
part instance217 : T39;
part instance218 : T39;
part instance219 : T39;
part instance220 : T39;
part instance221 : T39;
part instance222 : T39;
part instance223 : T39;
part instance224 : T39;
part instance225 : T39;
part instance226 : T39;
part instance227 : T39;
part instance228 : T39;
part instance229 : T39;
part instance230 : T39;
part instance231 : T39;
part instance232 : T39;
part instance233 : T39;
part instance234 : T39;
part instance235 : T39;
part instance236 : T39;
part instance237 : T39;
part instance238 : T39;
part instance239 : T39;
part instance240 : T39;
part instance241 : T39;
part instance242 : T39;
part instance243 : T39;
part instance244 : T39;
part instance245 : T39;
part instance246 : T39;
part instance247 : T39;
part instance248 : T39;
part instance249 : T39;
part instance250 : T39;
part instance251 : T39;
part instance252 : T39;
part instance253 : T39;
part instance254 : T39;
part instance255 : T39;
part instance256 : T39;
part instance257 : T39;
part instance258 : T39;
part instance259 : T39;
part instance260 : T39;
part instance261 : T39;
part instance262 : T39;
part instance263 : T39;
part instance264 : T39;
part instance265 : T39;
part instance266 : T39;
part instance267 : T39;
part instance268 : T39;
part instance269 : T39;
part instance270 : T39;
part instance271 : T39;
part instance272 : T39;
part instance273 : T39;
part instance274 : T39;
part instance275 : T39;
part instance276 : T39;
part instance277 : T39;
part instance278 : T39;
part instance279 : T39;
part instance280 : T39;
part instance281 : T39;
part instance282 : T39;
part instance283 : T39;
part instance284 : T39;
part instance285 : T39;
part instance286 : T39;
part instance287 : T39;
part instance288 : T39;
part instance289 : T39;
part instance290 : T39;
part instance291 : T39;
part instance292 : T39;
part instance293 : T39;
part instance294 : T39;
part instance295 : T39;
part instance296 : T39;
part instance297 : T39;
part instance298 : T39;
part instance299 : T39;
}
