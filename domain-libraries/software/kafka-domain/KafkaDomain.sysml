package KafkaDomain {
    import SoftwareCore::*;
    import MessagingDomain::*;
    import SerializationDomain::*;

    attribute def PartitionCount;

    part def KafkaTopic :> EventStream {
        attribute partitions : PartitionCount;
    }

    part def KafkaConsumerGroup {
        attribute groupName : Name;
    }

    part def KafkaBinding :> MessageBinding;
}
