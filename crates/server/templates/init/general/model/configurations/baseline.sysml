package BaselineConfiguration {
    doc /* Default system configuration. */

    private import SystemDefinitions::*;

    part baseline : System {
        doc /* Baseline configuration of the system. */
    }
}
